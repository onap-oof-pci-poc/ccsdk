module helloworld {
    yang-version 1;
    namespace "org:onap:ccsdk:features:sdnr:northbound:helloworld";
    prefix "helloworld";

    revision "2015-01-05" {
        description "Initial revision of helloworld model";
    }

    rpc greeting {
    	input {
    		leaf salutation {
    			type string;
    		}
    	}
    	output {
    		leaf response {
    			type string;
    		}
    	}
    }
}
